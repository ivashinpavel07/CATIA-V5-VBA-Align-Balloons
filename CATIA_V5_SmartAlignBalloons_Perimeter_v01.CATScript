'
' ****************************************************************************
' CATIA V5 SmartAlignBalloons Perimeter v0.1
'
' QUICK BALLOON DISTRIBUTION AROUND A PARALLELOGRAM
'
' Idea:
'   - user defines a parallelogram by THREE points:
'
'       P1 -------- P2
'       |            \
'       |             P3
'       P4 ----------/
'
'     First side:  P1 -> P2
'     Second side: P2 -> P3
'     Fourth point is calculated automatically:
'
'       P4 = P1 + (P3 - P2)
'
'   - all helper geometry is BLACK, DASHED, CATIA Line Type 2;
'   - both diagonals are created;
'   - diagonals split the parallelogram into four triangular regions;
'   - each Balloon is classified by the first point of its first Leader;
'   - Balloons from each triangle are distributed along that triangle's
'     OUTER parallelogram side;
'   - placement is shown STEP BY STEP, like SmartAlignBalloons v0.9;
'   - helper parallelogram + diagonals are deleted after distribution.
'
' The four regions are:
'
'             P1 ----------- P2
'              \ \    T1   / /
'               \ \       / /
'             T4 \ \  C  / / T2
'                 \ \   / /
'                  \ \ / /
'             P4 ----------- P3
'                       T3
'
' More precisely:
'   triangle P1-P2-C -> side P1-P2
'   triangle P2-P3-C -> side P2-P3
'   triangle P3-P4-C -> side P3-P4
'   triangle P4-P1-C -> side P4-P1
'
' Boundary points are assigned to the nearest corresponding perimeter side.
' Points outside the parallelogram are also assigned to the nearest side so no
' selected Balloon is lost.
'
' Optional dialogs:
'   1) Remove Positional Link?
'   2) Set Balloon AnchorPosition to catMiddleCenter?
'
' ****************************************************************************


Sub CATMain()

    If TypeName(CATIA.ActiveDocument) <> "DrawingDocument" Then

        MsgBox "Open a CATDrawing document before running SmartAlignBalloons Perimeter.", _
               vbExclamation, "SmartAlignBalloons Perimeter"

        Exit Sub

    End If


    Dim doc, sel, sheet, activeView, factory2D

    Set doc = CATIA.ActiveDocument
    Set sel = doc.Selection
    Set sheet = doc.Sheets.ActiveSheet
    Set activeView = sheet.Views.ActiveView
    Set factory2D = activeView.Factory2D


    ' =========================================================================
    ' 1. Select Balloons.
    ' =========================================================================
    Dim filter(0), status

    filter(0) = "DrawingText"

    sel.Clear

    status = sel.SelectElement3( _
        filter, _
        "Select DrawingText Balloons with Leaders, then validate the selection", _
        False, _
        CATMultiSelTriggWhenUserValidatesSelection, _
        False)

    If status = "Cancel" Or status = "Undo" Or status = "Redo" Then

        sel.Clear
        Exit Sub

    End If

    If sel.Count2 = 0 Then

        MsgBox "No DrawingText objects were selected.", _
               vbExclamation, "SmartAlignBalloons Perimeter"

        Exit Sub

    End If


    ' =========================================================================
    ' 2. Snapshot selected objects.
    ' =========================================================================
    Dim maxCount

    maxCount = sel.Count2


    Dim texts()
    Dim originalX(), originalY()
    Dim originalAnchor()
    Dim anchorX(), anchorY()
    Dim hadAssoc(), assocObjects()

    ReDim texts(maxCount - 1)
    ReDim originalX(maxCount - 1)
    ReDim originalY(maxCount - 1)
    ReDim originalAnchor(maxCount - 1)
    ReDim anchorX(maxCount - 1)
    ReDim anchorY(maxCount - 1)
    ReDim hadAssoc(maxCount - 1)
    ReDim assocObjects(maxCount - 1)


    Dim n, i
    Dim obj, leader, headPt, linkedObj

    n = 0


    For i = 1 To sel.Count2

        Set obj = sel.Item2(i).Value

        If TypeName(obj) = "DrawingText" Then

            If obj.Leaders.Count > 0 Then

                If MSA_TextBelongsToActiveView(obj, activeView) Then

                    Set texts(n) = obj

                    originalX(n) = CDbl(obj.X)
                    originalY(n) = CDbl(obj.Y)

                    On Error Resume Next

                    Err.Clear
                    originalAnchor(n) = CLng(obj.AnchorPosition)

                    If Err.Number <> 0 Then

                        Err.Clear
                        originalAnchor(n) = -1

                    End If

                    On Error GoTo 0


                    Set leader = obj.Leaders.Item(1)

                    headPt = MSA_GetLeaderHeadPoint(leader)

                    anchorX(n) = CDbl(headPt(0))
                    anchorY(n) = CDbl(headPt(1))


                    hadAssoc(n) = False
                    Set linkedObj = Nothing

                    On Error Resume Next

                    Err.Clear
                    Set linkedObj = obj.AssociativeElement

                    If Err.Number = 0 Then

                        If Not linkedObj Is Nothing Then

                            hadAssoc(n) = True
                            Set assocObjects(n) = linkedObj

                        End If

                    End If

                    Err.Clear

                    On Error GoTo 0


                    n = n + 1

                End If

            End If

        End If

    Next


    sel.Clear


    If n < 2 Then

        MsgBox "Select at least two DrawingText objects with Leaders in the active view.", _
               vbExclamation, "SmartAlignBalloons Perimeter"

        Exit Sub

    End If


    ' =========================================================================
    ' 3. User options.
    ' =========================================================================
    Dim linkChoice

    linkChoice = MsgBox( _
        "Remove Positional Link from the selected Balloons before alignment?" & vbCrLf & vbCrLf & _
        "YES  - remove Positional Links." & vbCrLf & _
        "       Recommended if some Balloons refuse to move." & vbCrLf & vbCrLf & _
        "NO   - keep Positional Links unchanged." & vbCrLf & vbCrLf & _
        "CANCEL - stop the macro.", _
        vbYesNoCancel + vbQuestion, _
        "SmartAlignBalloons Perimeter - Positional Link")

    If linkChoice = vbCancel Then Exit Sub


    Dim centerChoice

    centerChoice = MsgBox( _
        "Set Anchor Point of the selected Balloon texts to MIDDLE CENTER?" & vbCrLf & vbCrLf & _
        "YES  - set AnchorPosition = catMiddleCenter." & vbCrLf & _
        "       Recommended for circular Balloons." & vbCrLf & vbCrLf & _
        "NO   - preserve the current Anchor Point." & vbCrLf & vbCrLf & _
        "CANCEL - stop the macro.", _
        vbYesNoCancel + vbQuestion, _
        "SmartAlignBalloons Perimeter - Balloon Center")

    If centerChoice = vbCancel Then Exit Sub


    ' =========================================================================
    ' 4. Define FIRST side P1 -> P2 with black dashed rubber-band line.
    ' =========================================================================
    Dim p1(1), p2(1), p3(1), p4(1)

    status = doc.Indicate2D( _
        "Perimeter: click P1 - start of the first side", _
        p1)

    If status = "Cancel" Or status = "Undo" Or status = "Redo" Then Exit Sub


    Dim line1, line2, line3, line4, diag1, diag2

    Set line1 = Nothing
    Set line2 = Nothing
    Set line3 = Nothing
    Set line4 = Nothing
    Set diag1 = Nothing
    Set diag2 = Nothing


    If Not MSA_GetRubberBandPoint( _
        doc, sel, factory2D, _
        CDbl(p1(0)), CDbl(p1(1)), _
        "Perimeter: move cursor for side P1-P2; click P2", _
        p2, line1) Then

        Call MSA_DeleteAllFrameLines(sel, line1, line2, line3, line4, diag1, diag2)
        Exit Sub

    End If


    If Not MSA_VectorIsValid(p1(0), p1(1), p2(0), p2(1)) Then

        Call MSA_DeleteAllFrameLines(sel, line1, line2, line3, line4, diag1, diag2)

        MsgBox "The first side is too short.", _
               vbExclamation, "SmartAlignBalloons Perimeter"

        Exit Sub

    End If


    ' =========================================================================
    ' 5. Define SECOND side P2 -> P3.
    '    It starts from the endpoint of the first side.
    ' =========================================================================
    If Not MSA_GetRubberBandPoint( _
        doc, sel, factory2D, _
        CDbl(p2(0)), CDbl(p2(1)), _
        "Perimeter: move cursor for side P2-P3; click P3", _
        p3, line2) Then

        Call MSA_DeleteAllFrameLines(sel, line1, line2, line3, line4, diag1, diag2)
        Exit Sub

    End If


    If Not MSA_VectorIsValid(p2(0), p2(1), p3(0), p3(1)) Then

        Call MSA_DeleteAllFrameLines(sel, line1, line2, line3, line4, diag1, diag2)

        MsgBox "The second side is too short.", _
               vbExclamation, "SmartAlignBalloons Perimeter"

        Exit Sub

    End If


    ' =========================================================================
    ' 6. Calculate P4 and validate parallelogram.
    '
    '       P4 = P1 + P3 - P2
    ' =========================================================================
    p4(0) = CDbl(p1(0)) + CDbl(p3(0)) - CDbl(p2(0))
    p4(1) = CDbl(p1(1)) + CDbl(p3(1)) - CDbl(p2(1))


    Dim areaCross

    areaCross = MSA_Cross( _
        CDbl(p2(0)) - CDbl(p1(0)), _
        CDbl(p2(1)) - CDbl(p1(1)), _
        CDbl(p3(0)) - CDbl(p2(0)), _
        CDbl(p3(1)) - CDbl(p2(1)))


    If Abs(areaCross) < 0.000001 Then

        Call MSA_DeleteAllFrameLines(sel, line1, line2, line3, line4, diag1, diag2)

        MsgBox "The two sides are collinear. A parallelogram cannot be created.", _
               vbExclamation, "SmartAlignBalloons Perimeter"

        Exit Sub

    End If


    ' =========================================================================
    ' 7. Create remaining sides and BOTH diagonals.
    ' =========================================================================
    Set line3 = MSA_CreateFrameLine( _
        factory2D, sel, _
        CDbl(p3(0)), CDbl(p3(1)), _
        CDbl(p4(0)), CDbl(p4(1)), _
        "MSA_PERIMETER_SIDE_3")

    Set line4 = MSA_CreateFrameLine( _
        factory2D, sel, _
        CDbl(p4(0)), CDbl(p4(1)), _
        CDbl(p1(0)), CDbl(p1(1)), _
        "MSA_PERIMETER_SIDE_4")

    Set diag1 = MSA_CreateFrameLine( _
        factory2D, sel, _
        CDbl(p1(0)), CDbl(p1(1)), _
        CDbl(p3(0)), CDbl(p3(1)), _
        "MSA_PERIMETER_DIAGONAL_1")

    Set diag2 = MSA_CreateFrameLine( _
        factory2D, sel, _
        CDbl(p2(0)), CDbl(p2(1)), _
        CDbl(p4(0)), CDbl(p4(1)), _
        "MSA_PERIMETER_DIAGONAL_2")


    On Error Resume Next
    CATIA.ActiveWindow.ActiveViewer.Update
    Err.Clear
    On Error GoTo 0


    ' =========================================================================
    ' 8. Apply optional Balloon settings only AFTER all three geometry clicks.
    '    Therefore cancelling the parallelogram creation does not alter Balloons.
    ' =========================================================================
    Dim linksWereRemoved
    Dim removedLinks

    linksWereRemoved = False
    removedLinks = 0


    If linkChoice = vbYes Then

        removedLinks = MSA_RemovePositionalLinks(texts, n, activeView, sel)
        linksWereRemoved = True

        ' CATIA may rebuild annotation geometry after association removal.
        Call MSA_RefreshLeaderHeadPoints(texts, anchorX, anchorY, n)

    End If


    If centerChoice = vbYes Then

        Call MSA_SetMiddleCenter(texts, n)

    End If


    ' =========================================================================
    ' 9. Center of parallelogram = intersection of diagonals.
    ' =========================================================================
    Dim cx, cy

    cx = (CDbl(p1(0)) + CDbl(p3(0))) / 2
    cy = (CDbl(p1(1)) + CDbl(p3(1))) / 2


    ' =========================================================================
    ' 10. Classify every Leader anchor into one of four triangle regions.
    '
    ' group 0 -> side P1-P2
    ' group 1 -> side P2-P3
    ' group 2 -> side P3-P4
    ' group 3 -> side P4-P1
    ' =========================================================================
    Dim groupOf()
    Dim sideCount(3)
    Dim outsideCount
    Dim groupIndex

    ReDim groupOf(n - 1)

    For groupIndex = 0 To 3
        sideCount(groupIndex) = 0
    Next

    outsideCount = 0


    For i = 0 To n - 1

        groupIndex = MSA_ClassifyAnchor( _
            CDbl(anchorX(i)), CDbl(anchorY(i)), _
            CDbl(p1(0)), CDbl(p1(1)), _
            CDbl(p2(0)), CDbl(p2(1)), _
            CDbl(p3(0)), CDbl(p3(1)), _
            CDbl(p4(0)), CDbl(p4(1)), _
            cx, cy, _
            outsideCount)

        groupOf(i) = groupIndex
        sideCount(groupIndex) = sideCount(groupIndex) + 1

    Next


    CATIA.StatusBar = _
        "Perimeter groups: " & _
        CStr(sideCount(0)) & " / " & _
        CStr(sideCount(1)) & " / " & _
        CStr(sideCount(2)) & " / " & _
        CStr(sideCount(3)) & _
        "   Outside assigned to nearest side: " & CStr(outsideCount)


    ' =========================================================================
    ' 11. STEP-BY-STEP distribution around the perimeter.
    '
    ' The direction follows the perimeter:
    '   P1 -> P2 -> P3 -> P4 -> P1
    ' =========================================================================

    Call MSA_AlignGroupStepByStep( _
        texts, anchorX, anchorY, groupOf, n, 0, _
        CDbl(p1(0)), CDbl(p1(1)), _
        CDbl(p2(0)), CDbl(p2(1)), _
        1)

    Call MSA_AlignGroupStepByStep( _
        texts, anchorX, anchorY, groupOf, n, 1, _
        CDbl(p2(0)), CDbl(p2(1)), _
        CDbl(p3(0)), CDbl(p3(1)), _
        2)

    Call MSA_AlignGroupStepByStep( _
        texts, anchorX, anchorY, groupOf, n, 2, _
        CDbl(p3(0)), CDbl(p3(1)), _
        CDbl(p4(0)), CDbl(p4(1)), _
        3)

    Call MSA_AlignGroupStepByStep( _
        texts, anchorX, anchorY, groupOf, n, 3, _
        CDbl(p4(0)), CDbl(p4(1)), _
        CDbl(p1(0)), CDbl(p1(1)), _
        4)


    ' =========================================================================
    ' 12. Helper frame disappears only after all Balloons are placed.
    ' =========================================================================
    Call MSA_DeleteAllFrameLines(sel, line1, line2, line3, line4, diag1, diag2)


    CATIA.RefreshDisplay = True

    On Error Resume Next
    CATIA.ActiveWindow.ActiveViewer.Update
    Err.Clear
    On Error GoTo 0


    If linksWereRemoved Then

        CATIA.StatusBar = _
            "SmartAlignBalloons Perimeter: done. " & CStr(n) & _
            " Balloons aligned; Positional Links removed."

    Else

        CATIA.StatusBar = _
            "SmartAlignBalloons Perimeter: done. " & CStr(n) & _
            " Balloons aligned; Positional Links kept."

    End If


End Sub



' =============================================================================
' Rubber-band creation of ONE side.
'
' startX/startY are already fixed.
' The function:
'   - creates a black dashed temporary Line2D immediately;
'   - recreates it as the mouse moves;
'   - on click returns the final point and leaves the final line in the view.
'
' Result:
'   True  -> point accepted
'   False -> cancelled
' =============================================================================
Function MSA_GetRubberBandPoint( _
    doc, sel, factory2D, _
    startX, startY, _
    promptText, _
    ByRef outPt, _
    ByRef lineObj)

    Dim pointFilter(0)
    Dim mousePt(1)
    Dim objectSelected
    Dim status

    Dim lastX, lastY
    Dim moveDX, moveDY
    Dim minMove

    pointFilter(0) = "Point2D"

    lastX = startX
    lastY = startY

    minMove = 0.15


    Set lineObj = MSA_CreateFrameLine( _
        factory2D, sel, _
        startX, startY, _
        startX + 0.01, startY, _
        "MSA_PERIMETER_RUBBERBAND")


    If lineObj Is Nothing Then

        MSA_GetRubberBandPoint = False
        Exit Function

    End If


    On Error Resume Next

    Err.Clear

    status = sel.IndicateOrSelectElement2D( _
        promptText, _
        pointFilter, _
        False, _
        False, _
        True, _
        objectSelected, _
        mousePt)


    If Err.Number <> 0 Then

        ' Fallback for V5 versions where MouseMove callback is unavailable.
        Err.Clear
        On Error GoTo 0

        Call MSA_DeleteGuide(sel, lineObj)

        status = doc.Indicate2D(promptText, mousePt)

        If status = "Cancel" Or status = "Undo" Or status = "Redo" Then

            Set lineObj = Nothing
            MSA_GetRubberBandPoint = False
            Exit Function

        End If

        outPt(0) = CDbl(mousePt(0))
        outPt(1) = CDbl(mousePt(1))

        Set lineObj = MSA_CreateFrameLine( _
            factory2D, sel, _
            startX, startY, _
            CDbl(outPt(0)), CDbl(outPt(1)), _
            "MSA_PERIMETER_FIXED_SIDE")

        MSA_GetRubberBandPoint = True
        Exit Function

    End If


    On Error GoTo 0


    Do

        If status = "MouseMove" Then

            If Not objectSelected Then

                moveDX = CDbl(mousePt(0)) - lastX
                moveDY = CDbl(mousePt(1)) - lastY

                If (moveDX * moveDX + moveDY * moveDY) >= _
                   (minMove * minMove) Then

                    If MSA_VectorIsValid( _
                        startX, startY, _
                        mousePt(0), mousePt(1)) Then

                        Call MSA_DeleteGuide(sel, lineObj)

                        Set lineObj = MSA_CreateFrameLine( _
                            factory2D, sel, _
                            startX, startY, _
                            CDbl(mousePt(0)), CDbl(mousePt(1)), _
                            "MSA_PERIMETER_RUBBERBAND")

                        lastX = CDbl(mousePt(0))
                        lastY = CDbl(mousePt(1))

                        On Error Resume Next

                        CATIA.ActiveWindow.ActiveViewer.Update

                        Err.Clear

                        On Error GoTo 0

                    End If

                End If

            End If


            On Error Resume Next

            Err.Clear

            status = sel.IndicateOrSelectElement2D( _
                promptText, _
                pointFilter, _
                False, _
                False, _
                True, _
                objectSelected, _
                mousePt)

            If Err.Number <> 0 Then

                Err.Clear
                status = "Cancel"

            End If

            On Error GoTo 0


        ElseIf status = "Normal" Then

            If objectSelected Then

                On Error Resume Next

                Dim selectedPoint

                Set selectedPoint = sel.Item2(1).Value

                selectedPoint.GetCoordinates mousePt

                sel.Clear

                Err.Clear

                On Error GoTo 0

            End If


            outPt(0) = CDbl(mousePt(0))
            outPt(1) = CDbl(mousePt(1))


            ' Recreate one last exact fixed line at the click position.
            Call MSA_DeleteGuide(sel, lineObj)

            Set lineObj = MSA_CreateFrameLine( _
                factory2D, sel, _
                startX, startY, _
                CDbl(outPt(0)), CDbl(outPt(1)), _
                "MSA_PERIMETER_FIXED_SIDE")


            MSA_GetRubberBandPoint = True
            Exit Function


        ElseIf status = "Cancel" Or status = "Undo" Or status = "Redo" Then

            Call MSA_DeleteGuide(sel, lineObj)

            Set lineObj = Nothing

            MSA_GetRubberBandPoint = False
            Exit Function


        Else

            Call MSA_DeleteGuide(sel, lineObj)

            Set lineObj = Nothing

            MSA_GetRubberBandPoint = False
            Exit Function

        End If

    Loop

End Function



' =============================================================================
' Create black dashed helper geometry.
'
' These values were verified in the working diagnostic version:
'
'   Color    = RGB 0,0,0
'   LineType = 2
'   Width    = 1
' =============================================================================
Function MSA_CreateFrameLine(factory2D, sel, x1, y1, x2, y2, objectName)

    Dim lineObj
    Dim vis

    Set lineObj = Nothing


    On Error Resume Next

    Err.Clear


    Set lineObj = factory2D.CreateLine(x1, y1, x2, y2)


    If Err.Number <> 0 Then

        Err.Clear
        Set lineObj = Nothing

        On Error GoTo 0

        Set MSA_CreateFrameLine = lineObj
        Exit Function

    End If


    lineObj.Name = objectName


    sel.Clear
    sel.Add lineObj


    Set vis = sel.VisProperties


    vis.SetRealColor 0, 0, 0, 0
    vis.SetRealLineType 2, 0
    vis.SetRealWidth 1, 0


    sel.Clear


    Err.Clear

    On Error GoTo 0


    Set MSA_CreateFrameLine = lineObj

End Function



' =============================================================================
' Delete one guide Line2D.
' =============================================================================
Sub MSA_DeleteGuide(sel, lineObj)

    If lineObj Is Nothing Then Exit Sub


    On Error Resume Next

    Err.Clear

    sel.Clear
    sel.Add lineObj
    sel.Delete
    sel.Clear

    Err.Clear

    On Error GoTo 0

End Sub



' =============================================================================
' Delete all six helper lines.
' =============================================================================
Sub MSA_DeleteAllFrameLines(sel, line1, line2, line3, line4, diag1, diag2)

    Call MSA_DeleteGuide(sel, line1)
    Call MSA_DeleteGuide(sel, line2)
    Call MSA_DeleteGuide(sel, line3)
    Call MSA_DeleteGuide(sel, line4)
    Call MSA_DeleteGuide(sel, diag1)
    Call MSA_DeleteGuide(sel, diag2)

End Sub



' =============================================================================
' Classify one anchor into one of four triangles.
'
' If point belongs to exactly one triangle -> use that group.
'
' If it lies on a diagonal/boundary and therefore belongs to more than one
' triangle -> choose the nearest corresponding outer side.
'
' If point lies outside the parallelogram -> also choose nearest outer side and
' increment outsideCount.
' =============================================================================
Function MSA_ClassifyAnchor( _
    px, py, _
    p1x, p1y, _
    p2x, p2y, _
    p3x, p3y, _
    p4x, p4y, _
    cx, cy, _
    ByRef outsideCount)

    Dim inside0, inside1, inside2, inside3
    Dim matches

    inside0 = MSA_PointInTriangle(px, py, p1x, p1y, p2x, p2y, cx, cy)
    inside1 = MSA_PointInTriangle(px, py, p2x, p2y, p3x, p3y, cx, cy)
    inside2 = MSA_PointInTriangle(px, py, p3x, p3y, p4x, p4y, cx, cy)
    inside3 = MSA_PointInTriangle(px, py, p4x, p4y, p1x, p1y, cx, cy)


    matches = 0

    If inside0 Then matches = matches + 1
    If inside1 Then matches = matches + 1
    If inside2 Then matches = matches + 1
    If inside3 Then matches = matches + 1


    If matches = 1 Then

        If inside0 Then
            MSA_ClassifyAnchor = 0
        ElseIf inside1 Then
            MSA_ClassifyAnchor = 1
        ElseIf inside2 Then
            MSA_ClassifyAnchor = 2
        Else
            MSA_ClassifyAnchor = 3
        End If

        Exit Function

    End If


    If matches = 0 Then
        outsideCount = outsideCount + 1
    End If


    ' Boundary or outside:
    ' use nearest perimeter side.
    MSA_ClassifyAnchor = MSA_NearestSide( _
        px, py, _
        p1x, p1y, _
        p2x, p2y, _
        p3x, p3y, _
        p4x, p4y)

End Function



' =============================================================================
' Point-in-triangle test using oriented cross products.
' Includes points on triangle edges.
' =============================================================================
Function MSA_PointInTriangle(px, py, ax, ay, bx, by, cx, cy)

    Dim c1, c2, c3
    Dim eps

    eps = 0.000001


    c1 = MSA_Cross( _
        bx - ax, by - ay, _
        px - ax, py - ay)

    c2 = MSA_Cross( _
        cx - bx, cy - by, _
        px - bx, py - by)

    c3 = MSA_Cross( _
        ax - cx, ay - cy, _
        px - cx, py - cy)


    If (c1 >= -eps And c2 >= -eps And c3 >= -eps) Or _
       (c1 <= eps And c2 <= eps And c3 <= eps) Then

        MSA_PointInTriangle = True

    Else

        MSA_PointInTriangle = False

    End If

End Function



' =============================================================================
' Return nearest parallelogram perimeter side: 0..3.
' =============================================================================
Function MSA_NearestSide( _
    px, py, _
    p1x, p1y, _
    p2x, p2y, _
    p3x, p3y, _
    p4x, p4y)

    Dim d0, d1, d2, d3
    Dim bestSide, bestD


    d0 = MSA_PointSegmentDistanceSquared(px, py, p1x, p1y, p2x, p2y)
    d1 = MSA_PointSegmentDistanceSquared(px, py, p2x, p2y, p3x, p3y)
    d2 = MSA_PointSegmentDistanceSquared(px, py, p3x, p3y, p4x, p4y)
    d3 = MSA_PointSegmentDistanceSquared(px, py, p4x, p4y, p1x, p1y)


    bestSide = 0
    bestD = d0

    If d1 < bestD Then
        bestSide = 1
        bestD = d1
    End If

    If d2 < bestD Then
        bestSide = 2
        bestD = d2
    End If

    If d3 < bestD Then
        bestSide = 3
        bestD = d3
    End If


    MSA_NearestSide = bestSide

End Function



' =============================================================================
' Squared distance from point P to segment AB.
' =============================================================================
Function MSA_PointSegmentDistanceSquared(px, py, ax, ay, bx, by)

    Dim vx, vy
    Dim wx, wy
    Dim len2
    Dim t
    Dim qx, qy
    Dim dx, dy


    vx = bx - ax
    vy = by - ay

    wx = px - ax
    wy = py - ay

    len2 = vx * vx + vy * vy


    If len2 < 0.000000001 Then

        dx = px - ax
        dy = py - ay

        MSA_PointSegmentDistanceSquared = dx * dx + dy * dy
        Exit Function

    End If


    t = (wx * vx + wy * vy) / len2


    If t < 0 Then t = 0
    If t > 1 Then t = 1


    qx = ax + t * vx
    qy = ay + t * vy


    dx = px - qx
    dy = py - qy


    MSA_PointSegmentDistanceSquared = dx * dx + dy * dy

End Function



' =============================================================================
' Align one triangle group along its corresponding perimeter side.
'
' Same iterative SmartAlign logic as the stable v0.9:
'
'   target 1 -> evaluate all remaining group Balloons -> move one -> refresh
'   target 2 -> evaluate remaining -> move one -> refresh
'   ...
'
' groupIndex:
'   0 = side P1-P2
'   1 = side P2-P3
'   2 = side P3-P4
'   3 = side P4-P1
' =============================================================================
Sub MSA_AlignGroupStepByStep( _
    texts, anchorX, anchorY, groupOf, totalCount, groupIndex, _
    startX, startY, endX, endY, sideNumber)

    Dim groupCount
    Dim i

    groupCount = 0


    For i = 0 To totalCount - 1

        If groupOf(i) = groupIndex Then
            groupCount = groupCount + 1
        End If

    Next


    If groupCount = 0 Then Exit Sub


    Dim dx, dy
    Dim len2
    Dim stepX, stepY


    dx = endX - startX
    dy = endY - startY

    len2 = dx * dx + dy * dy


    If len2 < 0.000001 Then Exit Sub


    stepX = dx / (groupCount + 1)
    stepY = dy / (groupCount + 1)


    Dim remaining()
    ReDim remaining(totalCount - 1)


    For i = 0 To totalCount - 1

        If groupOf(i) = groupIndex Then
            remaining(i) = True
        Else
            remaining(i) = False
        End If

    Next


    Dim slot
    Dim targetX, targetY

    Dim bestIndex
    Dim bestDot, bestB2

    Dim bx, by
    Dim b2
    Dim dotValue

    Dim candidateBetter
    Dim leftValue, rightValue

    Dim currentText


    CATIA.RefreshDisplay = True


    For slot = 1 To groupCount

        targetX = startX + stepX * slot
        targetY = startY + stepY * slot


        bestIndex = -1
        bestDot = 0
        bestB2 = 0


        For i = 0 To totalCount - 1

            If remaining(i) Then

                bx = anchorX(i) - targetX
                by = anchorY(i) - targetY

                b2 = bx * bx + by * by

                dotValue = dx * bx + dy * by


                candidateBetter = False


                If bestIndex < 0 Then

                    candidateBetter = True


                ElseIf b2 <= 0.000000001 Then

                    candidateBetter = False


                ElseIf bestB2 <= 0.000000001 Then

                    candidateBetter = True


                ElseIf dotValue < 0 And bestDot >= 0 Then

                    candidateBetter = True


                ElseIf dotValue >= 0 And bestDot < 0 Then

                    candidateBetter = False


                Else

                    leftValue = dotValue * dotValue * bestB2
                    rightValue = bestDot * bestDot * b2


                    If dotValue < 0 Then

                        If leftValue > rightValue Then
                            candidateBetter = True
                        End If

                    Else

                        If leftValue < rightValue Then
                            candidateBetter = True
                        End If

                    End If

                End If


                If candidateBetter Then

                    bestIndex = i
                    bestDot = dotValue
                    bestB2 = b2

                End If

            End If

        Next


        If bestIndex >= 0 Then

            Set currentText = texts(bestIndex)

            currentText.X = targetX
            currentText.Y = targetY

            remaining(bestIndex) = False


            CATIA.StatusBar = _
                "Perimeter side " & CStr(sideNumber) & _
                ": placing " & CStr(slot) & _
                " / " & CStr(groupCount)


            On Error Resume Next

            CATIA.ActiveWindow.ActiveViewer.Update

            Err.Clear

            On Error GoTo 0

        End If

    Next


    CATIA.RefreshDisplay = True

End Sub



' =============================================================================
' DrawingText / Leader helpers
' =============================================================================
Function MSA_GetLeaderHeadPoint(leader)

    Dim nbPts
    Dim pathPts()
    Dim outPt(1)
    Dim returnedPts


    nbPts = CLng(leader.NbPoint)


    If nbPts < 1 Then

        Err.Raise vbObjectError + 2101, _
                  "MSA_GetLeaderHeadPoint", _
                  "The selected DrawingLeader does not contain path points."

    End If


    ReDim pathPts((nbPts * 2) - 1)


    returnedPts = leader.GetPoints(pathPts)


    If returnedPts < 1 Then

        Err.Raise vbObjectError + 2102, _
                  "MSA_GetLeaderHeadPoint", _
                  "DrawingLeader.GetPoints returned no points."

    End If


    outPt(0) = CDbl(pathPts(0))
    outPt(1) = CDbl(pathPts(1))


    MSA_GetLeaderHeadPoint = outPt

End Function



Sub MSA_RefreshLeaderHeadPoints(texts, anchorX, anchorY, count)

    Dim i
    Dim leader
    Dim headPt


    For i = 0 To count - 1

        Set leader = texts(i).Leaders.Item(1)

        headPt = MSA_GetLeaderHeadPoint(leader)

        anchorX(i) = CDbl(headPt(0))
        anchorY(i) = CDbl(headPt(1))

    Next

End Sub



Sub MSA_SetMiddleCenter(texts, count)

    Dim i


    On Error Resume Next

    Err.Clear


    For i = 0 To count - 1

        Err.Clear

        ' catMiddleCenter = 5
        texts(i).AnchorPosition = 5

    Next


    Err.Clear

    On Error GoTo 0

End Sub



' =============================================================================
' Positional Link helpers
' =============================================================================
Function MSA_RemovePositionalLinks(texts, count, activeView, sel)

    Dim i
    Dim dmy
    Dim linkedObj
    Dim linkCount


    linkCount = 0


    For i = 0 To count - 1

        Set linkedObj = Nothing


        On Error Resume Next

        Err.Clear


        Set linkedObj = texts(i).AssociativeElement


        If Err.Number = 0 Then

            If Not linkedObj Is Nothing Then
                linkCount = linkCount + 1
            End If

        End If


        Err.Clear

        On Error GoTo 0

    Next


    On Error Resume Next

    Err.Clear


    CATIA.HSOSynchronized = False


    Set dmy = activeView.Texts.Add("MSA_POSLINK_TEMP", 0, 0)


    If Err.Number = 0 Then

        For i = 0 To count - 1

            Err.Clear

            texts(i).AssociativeElement = dmy

        Next


        sel.Clear
        sel.Add dmy
        sel.Delete
        sel.Clear

    End If


    CATIA.HSOSynchronized = True


    Err.Clear

    On Error GoTo 0


    MSA_RemovePositionalLinks = linkCount

End Function



Sub MSA_RestorePositionalLinks(texts, hadAssoc, assocObjects, count)

    Dim i


    On Error Resume Next

    Err.Clear


    CATIA.HSOSynchronized = False


    For i = 0 To count - 1

        If hadAssoc(i) Then

            Err.Clear

            texts(i).AssociativeElement = assocObjects(i)

        End If

    Next


    CATIA.HSOSynchronized = True


    Err.Clear

    On Error GoTo 0

End Sub



' =============================================================================
' Geometry helpers
' =============================================================================
Function MSA_Cross(ax, ay, bx, by)

    MSA_Cross = ax * by - ay * bx

End Function



Function MSA_VectorIsValid(x1, y1, x2, y2)

    Dim dx, dy


    dx = CDbl(x2) - CDbl(x1)
    dy = CDbl(y2) - CDbl(y1)


    MSA_VectorIsValid = ((dx * dx + dy * dy) > 0.000001)

End Function



Function MSA_TextBelongsToActiveView(txt, activeView)

    Dim txtView, parent1


    MSA_TextBelongsToActiveView = True


    On Error Resume Next

    Err.Clear


    Set parent1 = txt.Parent
    Set txtView = parent1.Parent


    If Err.Number = 0 Then

        If txtView.Name <> activeView.Name Then

            MSA_TextBelongsToActiveView = False

        End If

    End If


    Err.Clear

    On Error GoTo 0

End Function
